# Copyright (c) Microsoft Corporation. All rights reserved.
# Licensed under the MIT License.

import FreeCAD
from PySide import QtGui, QtCore
import qmt as QMT
reload(QMT)
import qmt.freecad.objectConstruction
reload(qmt.freecad.objectConstruction)
from qmt.freecad.objectConstruction import modelBuilder


buildModel = modelBuilder()
for i in range(len(buildModel.model.modelDict['buildOrder'])):
    partName = buildModel.model.modelDict['buildOrder'][str(i)]
    totalParts = len(buildModel.model.modelDict['buildOrder'])
    print('('+str(i+1)+'/'+str(totalParts)+') building part '+partName+'...')
    buildModel.buildPart(partName)
buildModel._collect_garbarge()
