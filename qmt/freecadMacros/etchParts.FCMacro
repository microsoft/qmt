# Copyright (c) Microsoft Corporation. All rights reserved.
# Licensed under the MIT License.
#
# Macro to take several parts and subtract them from a mask, creating a constructive
# build zone from a series of etch windows.
#

import FreeCAD
import Draft
from PySide import QtGui, QtCore
import qmt as QMT
reload(QMT)
import qmt.freecad.geomUtils
reload(qmt.freecad.geomUtils)
import qmt.freecad.sketchUtils
reload(qmt.freecad.sketchUtils)

from qmt.freecad.geomUtils import subtractParts
from qmt.freecad.sketchUtils import makeIntoSketch


class GuiClass(QtGui.QDialog):
    """"""
    def __init__(self):
        super(GuiClass, self).__init__()
        self.initUI()
    def initUI(self):
        self.result = False
        # create our window
        # define window		xLoc,yLoc,xDim,yDim
        self.setGeometry(	250, 250, 500, 180)
        self.setWindowTitle("Set the mask label for DXF Pruning")
        self.setWindowFlags(QtCore.Qt.WindowStaysOnTopHint)

        def vPix(elementNum):
            # compute the vertical pixel offset for a given element
            offset = 10
            lineWidth = 40
            return elementNum*lineWidth+offset
        
        # First, snag the selected layers to use for generating the pruned objects:
        selObjs = Gui.Selection.getSelection()
        self.selObjNames = []
        for obj in selObjs:
            self.selObjNames += [obj.Name]

        self.maskLabelLabel = QtGui.QLabel('Enter etch domain label:',self)
        self.maskLabelLabel.setFont('Courier')
        self.maskLabelLabel.move(20,vPix(1))
        self.maskLabel = QtGui.QLineEdit(self)
        self.maskLabel.setFixedWidth(190)
        self.maskLabel.move(220,vPix(1))
        self.maskLabel.setText('mask')

        self.OKButton = QtGui.QPushButton('OK', self)
        self.OKButton.move(20,vPix(3))
        self.OKButton.clicked.connect(self.onOK)
        self.CancelButton = QtGui.QPushButton("Cancel",self)
        self.CancelButton.move(220,vPix(3))
        self.CancelButton.clicked.connect(self.onCancel)

    def onOK(self):
        self.result = True
        self.close()
    def onCancel(self):
        self.result	= False
        self.close()
     

form = GuiClass()
form.exec_()

if not form.result:
    print 'Error with input!'
else:
    selObjNames = form.selObjNames
    etchDomainLabel = form.maskLabel.text()

selObjs = [FreeCAD.ActiveDocument.getObject(name) for name in selObjNames]
draftSelObjs = []
for obj in selObjs:
    draftSelObjs += [Draft.draftify(obj,delete=True)]
domainName = selObjNames[0]+'_buildZone'
etchDomainObj = FreeCAD.ActiveDocument.getObjectsByLabel(etchDomainLabel)[0]
etchedPart = subtractParts(etchDomainObj,draftSelObjs)
makeIntoSketch(etchedPart,sketchName=domainName)
