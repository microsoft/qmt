# Copyright (c) Microsoft Corporation. All rights reserved.
# Licensed under the MIT License.

#
# Macro to turn draft shapes into sketches. Also can optionally interpret a face 
# as an etch. To use, select the draft shapes you would like to convert and run 
# the macro.
#

import FreeCAD
from PySide import QtGui, QtCore
import qmt as QMT
reload(QMT)
import qmt.freecad.geomUtils
reload(qmt.freecad.geomUtils)
import qmt.freecad.sketchUtils
reload(qmt.freecad.sketchUtils)

from qmt.freecad.geomUtils import subtractParts
from qmt.freecad.sketchUtils import makeIntoSketch


class GuiClass(QtGui.QDialog):
    """"""
    def __init__(self):
        super(GuiClass, self).__init__()
        self.initUI()
    def initUI(self):
        self.result = False
        # create our window
        # define window		xLoc,yLoc,xDim,yDim
        self.setGeometry(	250, 250, 500, 180)
        self.setWindowTitle("Set the mask label for DXF Pruning")
        self.setWindowFlags(QtCore.Qt.WindowStaysOnTopHint)

        def vPix(elementNum):
            # compute the vertical pixel offset for a given element
            offset = 10
            lineWidth = 40
            return elementNum*lineWidth+offset
        
        # First, snag the selected layers to use for generating the pruned objects:
        selObjs = Gui.Selection.getSelection()
        self.selObjNames = []
        for obj in selObjs:
            self.selObjNames.append(obj.Name)
        
        self.etchCheckbox = QtGui.QCheckBox("Etch layer", self)
        self.etchCheckbox.move(20,vPix(0))

        self.maskLabelLabel = QtGui.QLabel('Enter etch domain label:',self)
        self.maskLabelLabel.setFont('Courier')
        self.maskLabelLabel.move(20,vPix(1))
        self.maskLabel = QtGui.QLineEdit(self)
        self.maskLabel.setFixedWidth(190)
        self.maskLabel.move(220,vPix(1))
        self.maskLabel.setText('mask')

        self.OKButton = QtGui.QPushButton('OK', self)
        self.OKButton.move(20,vPix(3))
        self.OKButton.clicked.connect(self.onOK)
        self.CancelButton = QtGui.QPushButton("Cancel",self)
        self.CancelButton.move(220,vPix(3))
        self.CancelButton.clicked.connect(self.onCancel)

    def onOK(self):
        self.result = True
        self.close()
    def onCancel(self):
        self.result	= False
        self.close()
     

form = GuiClass()
form.exec_()

if not form.result:
    print 'Error with input!'
else:
    selObjNames = form.selObjNames
    etchDomainLabel = form.maskLabel.text()
    shouldEtch = form.etchCheckbox.isChecked()

selObjs = [FreeCAD.ActiveDocument.getObject(name) for name in selObjNames]

if shouldEtch:
    sketchName = selObjNames[0]+'_sketch'
    etchDomainObj = FreeCAD.ActiveDocument.getObjectsByLabel(etchDomainLabel)[0]
    etchedPart = subtractParts(etchDomainObj,selObjs)
    makeIntoSketch(etchedPart,sketchName=sketchName)
else:
    for selObj in selObjs:
        sketchName = selObj.Name+'_sketch'
        makeIntoSketch(selObj,sketchName=sketchName)
