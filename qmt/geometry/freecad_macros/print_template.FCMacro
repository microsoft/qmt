# Copyright (c) Microsoft Corporation. All rights reserved.
# Licensed under the MIT License.

#
# Macro that prints a template to generate solids based on the selected 2D objects.
#

import json
import os

selObjs = Gui.Selection.getSelection()

print "Generating the mapping from labels to FreeCAD names:"
for selObj in selObjs:
    objLabel = selObj.Label
    objName = selObj.Name
    print objLabel + " " + objName
