# Copyright (c) Microsoft Corporation. All rights reserved.
# Licensed under the MIT License.

#
# Macro to prune a dxf import. To use, select the DXF layers that you want to 
# prune and run the macro. You will be asked to enter the label on a shape, which
# will be used as a mask.
#

from PySide import QtGui, QtCore
import numpy as np 
import Draft
import Part
from qmt.freecad import isNonempty,intersect,delete,findEdgeCycles,addCycleSketch,copy


class GuiClass(QtGui.QDialog):
    """"""
    def __init__(self):
        super(GuiClass, self).__init__()
        self.initUI()
    def initUI(self):
        self.result = False
        # create our window
        # define window		xLoc,yLoc,xDim,yDim
        self.setGeometry(	250, 250, 500, 150)
        self.setWindowTitle("Set the mask label for DXF Pruning")
        self.setWindowFlags(QtCore.Qt.WindowStaysOnTopHint)

        def vPix(elementNum):
            # compute the vertical pixel offset for a given element
            offset = 10
            lineWidth = 40
            return elementNum*lineWidth+offset
        
        # First, snag the selected layers to use for generating the pruned objects:
        selObjs = Gui.Selection.getSelection()
        self.selObjNames = []
        for obj in selObjs:
            self.selObjNames.append(obj.Name)
        
        # Next, specify the mask name:

        self.maskLabelLabel = QtGui.QLabel('Enter mask label:',self)
        self.maskLabelLabel.setFont('Courier')
        self.maskLabelLabel.move(20,vPix(1))
        self.maskLabel = QtGui.QLineEdit(self)
        self.maskLabel.setFixedWidth(190)
        self.maskLabel.move(220,vPix(1))
        self.maskLabel.setText('mask')

        self.OKButton = QtGui.QPushButton('OK', self)
        self.OKButton.move(20,vPix(2))
        self.OKButton.clicked.connect(self.onOK)
        self.CancelButton = QtGui.QPushButton("Cancel",self)
        self.CancelButton.move(220,vPix(2))
        self.CancelButton.clicked.connect(self.onCancel)

    def onFile(self):
        self.filePath = QtGui.QFileDialog.getOpenFileName()[0]
        self.filePathBox.setText(self.filePath)
    def onOK(self):
        self.result = True
        self.close()
    def onCancel(self):
        self.result	= False
        self.close()
    # def onGroupMenu(self,selectedText):
    #     self.groupLabel = selectedText

form = GuiClass()
form.exec_()

if not form.result:
    raise ValueError('Error with input!')
else:
    dxfLayerNames = form.selObjNames
    maskLabel = form.maskLabel.text()

survivingLayerDict = {}

mask = App.ActiveDocument.getObjectsByLabel(maskLabel)[0]
for layerName in dxfLayerNames:
    layerGroup = App.activeDocument().getObject(layerName)
    objsInLayer = layerGroup.OutList
    survivingLayerDict[layerName] = {}
    for j,obj in enumerate(objsInLayer):
        faceObj = copy(obj)
        if faceObj.Shape.ShapeType=='Wire' and not faceObj.Shape.isClosed():
            delete(faceObj)
            continue
        try: # Try to convert to a face
            faceObj.Shape = Part.Face(obj.Shape)
        except: # If we couldn't convert to face, print warning
            print 'WARNING: Not all DXF objects are recognized as complete.'
            delete(faceObj)
            continue
        intObj = intersect([mask,faceObj]) # intersect with mask
        delete(faceObj) # Delte the face
        if isNonempty(intObj): # If we have a finite intersection with the mask
            lineSegments, cycles = findEdgeCycles(intObj) # See what cycles are in the intersection object
            for i,cycle in enumerate(cycles): # For each cycle
                addCycleSketch(layerName+'_'+str(j)+'_'+str(i),App.ActiveDocument,cycle,lineSegments) # Make a new sketch
        delete(intObj) # Get rid of the intermediate intersection object. This cleans up spurious splines.
