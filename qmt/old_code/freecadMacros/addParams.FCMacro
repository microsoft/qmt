# Copyright (c) Microsoft Corporation. All rights reserved.
# Licensed under the MIT License.

#
# Macro that creates parameters in a spreadsheet and labels them for use.
#

from PySide import QtGui, QtCore
import numpy as np 
import json
import os
import qmt as QMT
reload(QMT)


class GuiClass(QtGui.QDialog):
    """"""
    def __init__(self):
        super(GuiClass, self).__init__()
        self.initUI()
    def initUI(self):
        self.result = False
        # create our window
        # define window		xLoc,yLoc,xDim,yDim
        self.setGeometry(	250, 250, 500, 170)
        self.setWindowTitle("Set up geometric parameters")
        self.setWindowFlags(QtCore.Qt.WindowStaysOnTopHint)
    
        def vPix(elementNum):
            # compute the vertical pixel offset for a given element
            offset = 10
            lineWidth = 40
            return elementNum*lineWidth+offset

        # parameter names  
        self.paramNamesLabel = QtGui.QLabel("Parameter names:", self)
        self.paramNamesLabel.setFont('Courier') 
        self.paramNamesLabel.move(20, vPix(0))

        self.paramNames = QtGui.QLineEdit(self)
        self.paramNames.setText('Param1,Param2, Param3')
        self.paramNames.setFixedWidth(200)
        self.paramNames.move(170, vPix(0))

        # parameter values  
        self.paramValsLabel = QtGui.QLabel("Parameter values:", self)
        self.paramValsLabel.setFont('Courier') 
        self.paramValsLabel.move(20, vPix(1))

        self.paramVals = QtGui.QLineEdit(self)
        self.paramVals.setText('1.0,2., 3.0')
        self.paramVals.setFixedWidth(200)
        self.paramVals.move(170, vPix(1))      

        # buttons:
        self.OKButton = QtGui.QPushButton('OK', self)
        self.OKButton.move(20,vPix(2))
        self.OKButton.clicked.connect(self.onOK)
        self.CancelButton = QtGui.QPushButton("Cancel",self)
        self.CancelButton.move(225,vPix(2))
        self.CancelButton.clicked.connect(self.onCancel)

    def onOK(self):
        self.result = True
        self.close()
    def onCancel(self):
        self.result	= False
        self.close()
form = GuiClass()
form.exec_()
if not form.result:
    print 'Error loading file!'
else:
    paramNames = form.paramNames.text()
    paramVals = form.paramVals.text()

fileName = App.ActiveDocument.modelFilePath.modelFilePath # need to have set this before

# All the parameters in our model are stored in a spreadsheet named "modelParams",
# which is mirrored to the model json file on disk. Load and update as needed:
paramVals = map(lambda x:np.float(x),map(lambda x: x.strip(' '),paramVals.split(',')))
paramNames = map(lambda x: x.strip(' '),paramNames.split(','))
newParamDict = dict(zip(paramNames,paramVals))
myModel = QMT.Model(modelPath=fileName)
myModel.loadModel()
myModel.modelDict['geometricParams'].update(newParamDict)
myModel.saveModel()
paramDict = myModel.modelDict['geometricParams']

# Now we have an updated json file on disk and also a current paramDict. So now
# we need to write this to a spreadsheet in FreeCAD and assign the proper labels.

# First, determine if we already have a spreadsheet:
objList = App.ActiveDocument.Objects
objNames = [x.Name for x in objList]
# If we do, delete it (we will rebuild from the json)
if 'modelParams' in objNames:
    App.ActiveDocument.removeObject('modelParams')
App.ActiveDocument.recompute()
App.ActiveDocument.addObject('Spreadsheet::Sheet','modelParams')
spreadSheet = App.ActiveDocument.modelParams
spreadSheet.set('A1', 'paramName')
spreadSheet.set('B1', 'paramValue')
spreadSheet.setColumnWidth('A', 200)
spreadSheet.setStyle('A1:B1', 'bold', 'add')

for i in range(len(paramDict)):
    key = paramDict.keys()[i]
    valStr = str(paramDict[key])
    spreadSheet.set('A'+str(i+2),key)
    spreadSheet.set('B'+str(i+2),valStr)
    spreadSheet.setAlias('B'+str(i+2), str(key))
App.ActiveDocument.recompute()
