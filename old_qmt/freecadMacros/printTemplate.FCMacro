# Copyright (c) Microsoft Corporation. All rights reserved.
# Licensed under the MIT License.

#
# Macro that prints a template to generate solids based on the selected 2D objects.
#

import json
import os

import qmt as QMT
reload(QMT)

selObjs = Gui.Selection.getSelection()


print "Generating template for building the solid:"
print "Available directives are: extrude, wire, wireShell, SAG, and lithography."
print "Available domainTypes are: semiconductor, dielectric, metalGate, and virtual."
print ""
print ""
for selObj in selObjs:
    objLabel = selObj.Label
    objName = selObj.Name
    print "runModel.addPart('"+objLabel+"','"+objName+"','extrude','dielectric',"
    print "                 material = 'SiO2',z0=-0.2,thickness=0.2,meshMaxSize=0.2)"
    print ""
