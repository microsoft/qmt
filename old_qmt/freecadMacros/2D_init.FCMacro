# Copyright (c) Microsoft Corporation. All rights reserved.
# Licensed under the MIT License.

#
# Macro that initializes a 2D simulation. To use, select a sketch that you
# would like to use as the simulation domain and run the macro.
#

import qmt.freecad.fileIO
reload(qmt.freecad.fileIO)
from qmt.freecad.fileIO import getModel
import qmt.freecad.geomUtils
reload(qmt.freecad.geomUtils)
from qmt.freecad.geomUtils import extrude
import FreeCAD
import FreeCADGui


myDoc = FreeCAD.ActiveDocument

# myDoc.addObject('Sketcher::SketchObject','twoDMasterSketch')
targetSketch = FreeCADGui.Selection.getSelection()[0]
extrude(targetSketch,10.,reversed=True,name=targetSketch.Name+'_pad')



myModel = getModel()
myModel.initialize2DSim() 
myModel.modelDict['freeCADInfo'][targetSketch.Name] = {'2DObject':{'label':targetSketch.Label,
                                                       'type':'background',
                                                       'physicsProps':{}}}
myModel.saveModel()
